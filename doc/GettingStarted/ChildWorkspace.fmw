FME workspace ChildWorkspace.fmw

Parameters:
- EurostatWebConnection = sejuva Eurostat_v1 (eea.eurostat)   # eea.eurostat.Eurostat_v1 Eurostat Connection
- Datasets = ORG_LSTSPEC,IRT_EURYLD_M   # Enter the datasets you want to read (comma seperated)
- Box = FME_DISCLOSURE_OPEN   # Optional
- FirstNObservations =   # First N Observations to read
- LastNObservations =   # Last N Observations to read
- StartPeriod =   # Enter the StartPeriod
- EndPeriod =   # Enter the EndPeriod

Creator
    GEOMTYPE = Geometry Object
    NUM = 1
    CREATED -> ParameterFetcher
Note: Expose dataset and the webconnection for editing
ParameterFetcher
    ATTR_LIST = _Datasets $(Datasets) _EurostatWebConnection $(EurostatWebConnection)
    -> StringReplacer
Note: Replace spaces in the webconnection with %20. (only required if the name contains spaces)
StringReplacer
    CASE = NO
    FIND_TEXT = " "
    NO_MATCH = _FME_NO_OP_
    REGEXP = NO
    REPLACE_TEXT = %20
    SRC_ATTRS = _EurostatWebConnection
    -> AttributeSplitter
Note: Split the datasets on a comma. This so more than one dataset can be read at a time.
AttributeSplitter
    ATTR_NAME = _Datasets
    DELIMITER = ,
    DROP_EMPTY_PARTS = No
    LIST_NAME = _Datasets
    TRIM_OPTION = Both
    -> ListExploder
Note: Expose the datasets from the created lists.
ListExploder
    ATTR_ACCUM_MODE = Merge List Attributes
    ATTR_CONFLICT_RES = Use List Attribute Values
    INDEX_ATTR = _element_index
    LIST_ATTR = _Datasets{}
    ELEMENTS -> FeatureReader [INITIATOR]
FeatureReader
    ATTRIBUTES = NRG_INF_EPC_a58f84d5,"DATAFLOW,""LAST UPDATE"",freq,siec,operator,unit,geo,TIME_PERIOD,OBS_VALUE,OBS_FLAG"
    ATTR_ACCUM_MODE = Only Use Result
    COMBINE_GEOM = Use Result
    DATASET = fme://eea.fme-eurostat.fme-eurostat/@Value(_Datasets).csv?id=@Value(_Datasets)&module=fmepy_eurostat.catalog&webservice=eea.eurostat.Eurostat&connection=@Value(_EurostatWebConnection)&end_period=$(EndPeriod)&first_n_observations=$(FirstNObservations)&last_n_observations=$(LastNObservations)&start_period=$(StartPeriod)
    EEA.EUROSTAT.EUROSTAT_CASE_SENSITIVE_FIELD_NAMES = Yes
    EEA.EUROSTAT.EUROSTAT_CHUNK_SIZE = 100000
    EEA.EUROSTAT.EUROSTAT_DATE_INPUT_FORMAT = %d/%m/%y2099 %H:%M:%S$
    EEA.EUROSTAT.EUROSTAT_DELIMITER = ,
    EEA.EUROSTAT.EUROSTAT_ENCODING = UTF-8
    EEA.EUROSTAT.EUROSTAT_ENFORCE_STRICT_SCHEMA = No
    EEA.EUROSTAT.EUROSTAT_FEATURE_TYPE_NAME = FILE_NAME
    EEA.EUROSTAT.EUROSTAT_FIELD_NAMES_LINE = 1
    EEA.EUROSTAT.EUROSTAT_FIELD_QUALIFIER_CHARACTER = "
    EEA.EUROSTAT.EUROSTAT_FIELD_QUALIFIER_ESCAPE_CHARACTER = "
    EEA.EUROSTAT.EUROSTAT_PRESERVE_SOURCE_ENCODING = No
    EEA.EUROSTAT.EUROSTAT_QUERY_FEATURE_TYPES_FOR_MERGE_FILTERS = Yes
    EEA.EUROSTAT.EUROSTAT_READ_EMPTY_VALUES_AS = Null
    EEA.EUROSTAT.EUROSTAT_READ_SKIPPED_LINES = No
    EEA.EUROSTAT.EUROSTAT_REPLACE_ATTR_NAME_INVALID_CHARS = No
    EEA.EUROSTAT.EUROSTAT_SCAN_ADDITIONAL_FIELDS = No
    EEA.EUROSTAT.EUROSTAT_SCAN_TYPES = Yes
    EEA.EUROSTAT.EUROSTAT_SKIP_DUPLICATE_DELIMITERS = No
    EEA.EUROSTAT.EUROSTAT_STRING_TYPE_ATTRIBUTE_HANDLING = STANDARD_TYPES
    EEA.EUROSTAT.EUROSTAT_SUPPORTED_READER_ARCHIVE_EXTENSIONS = csv.gz,txt.gz
    EEA.EUROSTAT.EUROSTAT_TRIM_FEATURE_TYPE_NAME = Yes
    EEA.EUROSTAT.EUROSTAT_TRIM_FIELD_NAME_QUALIFIERS = Yes
    EEA.EUROSTAT.EUROSTAT_TRIM_FIELD_NAME_WHITESPACE = Yes
    EEA.EUROSTAT.EUROSTAT_TRIM_FIELD_VALUE_QUALIFIERS = Yes
    EEA.EUROSTAT.EUROSTAT_TYPE_ATTRIBUTE_HANDLING = STANDARD_TYPES
    EEA.EUROSTAT.EUROSTAT_USE_CUSTOM_SCHEMA = No
    FORMAT = EEA.EUROSTAT.EUROSTAT
    INTERACT = NONE
    OUTPUT_FEATURES_DISPLAY = Schema and Data Features
