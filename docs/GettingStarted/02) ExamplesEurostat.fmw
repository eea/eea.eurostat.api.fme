FME workspace 02) ExamplesEurostat.fmw

Parameters:
- LANG = en   # NO LOOKUP,NO%English,en%Francais,fr%Deutsch,de Select Language
- GEO_GRP = FME_DISCLOSURE_OPEN   # Geometry selection
- GEOTYPE = RG   # Select geometry type
- PROJ = 4326
- RES = 01M   # 60 m,60M%20 m,20M%10 m,10M%3 m,03M%1 m,01M Select surface resolution
- SourceDataset_EEA.EUROSTAT.EUROSTAT_9 = fme://eea.fme-eurostat.fme-eurostat/ORG_LSTSPEC_d8bb3647.csv?id=ORG_LSTSPEC&module=fmepy_eurostat.catalog&webservice=eea.eurostat.Eurostat&connection=sejuva%20Eurostat_v1%20(eea.eurostat)&first_n_observations=1&last_n_observations=1   # Select a Dataflow
- SourceDataset_EEA.EUROSTAT.EUROSTAT_13 = fme://eea.fme-eurostat.fme-eurostat/IRT_EURYLD_D_8f338484.csv?id=IRT_EURYLD_D&module=fmepy_eurostat.catalog&webservice=eea.eurostat.Eurostat&connection=sejuva%20Eurostat_v1%20(eea.eurostat)&end_period=2023-03-29&start_period=2023-03-28   # Select a Dataflow
- SourceDataset_EEA.EUROSTAT.EUROSTAT_11 = fme://eea.fme-eurostat.fme-eurostat/HLTH_EHIS_SK3U_41296021.csv?id=HLTH_EHIS_SK3U&module=fmepy_eurostat.catalog&webservice=eea.eurostat.Eurostat&connection=sejuva%20Eurostat_v1%20(eea.eurostat)&end_period=2014&start_period=2014   # Select a Dataflow
- SourceDataset_EEA.EUROSTAT.EUROSTAT_10 = fme://eea.fme-eurostat.fme-eurostat/IRT_EURYLD_M_ed470f15.csv?id=IRT_EURYLD_M&module=fmepy_eurostat.catalog&webservice=eea.eurostat.Eurostat&connection=sejuva%20Eurostat_v1%20(eea.eurostat)&end_period=2016-06&start_period=2016-04   # Select a Dataflow
- SourceDataset_EEA.EUROSTAT.EUROSTAT_12 = fme://eea.fme-eurostat.fme-eurostat/IRT_EURYLD_M_970c2537.csv?id=IRT_EURYLD_M&module=fmepy_eurostat.catalog&webservice=eea.eurostat.Eurostat&connection=sejuva%20Eurostat_v1%20(eea.eurostat)&end_period=2016-M06&start_period=2016-M04   # Select a Dataflow
- SourceDataset_EEA.EUROSTAT.EUROSTAT_8 = fme://eea.fme-eurostat.fme-eurostat/MAR_GO_QM_EE.csv?id=MAR_GO_QM_EE&module=fmepy_eurostat.catalog&webservice=eea.eurostat.Eurostat&connection=sejuva%20Eurostat_v1%20(eea.eurostat)   # Select a Dataflow
- SourceDataset_EEA.EUROSTAT.EUROSTAT = fme://eea.fme-eurostat.fme-eurostat/ORG_LSTSPEC.csv?id=ORG_LSTSPEC&module=fmepy_eurostat.catalog&webservice=eea.eurostat.Eurostat&connection=sejuva%20Eurostat_v1%20(eea.eurostat)   # Select a Dataflow

Readers:
- EEA.EUROSTAT.EUROSTAT_1: EEA.EUROSTAT.EUROSTAT from $(SourceDataset_EEA.EUROSTAT.EUROSTAT)
- EEA.EUROSTAT.EUROSTAT_2: EEA.EUROSTAT.EUROSTAT from $(SourceDataset_EEA.EUROSTAT.EUROSTAT_9)
- EEA.EUROSTAT.EUROSTAT_3: EEA.EUROSTAT.EUROSTAT from $(SourceDataset_EEA.EUROSTAT.EUROSTAT_13)
- EEA.EUROSTAT.EUROSTAT_4: EEA.EUROSTAT.EUROSTAT from $(SourceDataset_EEA.EUROSTAT.EUROSTAT_11)
- EEA.EUROSTAT.EUROSTAT_6: EEA.EUROSTAT.EUROSTAT from $(SourceDataset_EEA.EUROSTAT.EUROSTAT_10)
- EEA.EUROSTAT.EUROSTAT_7: EEA.EUROSTAT.EUROSTAT from $(SourceDataset_EEA.EUROSTAT.EUROSTAT_12)
- EEA.EUROSTAT.EUROSTAT_5: EEA.EUROSTAT.EUROSTAT from $(SourceDataset_EEA.EUROSTAT.EUROSTAT_8)

Inspector_3

Bookmark: 1) Standard reading and enriching the data from Eurostat
Note: Organic Livestock
ORG_LSTSPEC (reader EEA.EUROSTAT.EUROSTAT_1)
    attributes: DATAFLOW string, LAST UPDATE datetime, freq string, animals string, unit string, geo string, TIME_PERIOD uint32, OBS_VALUE uint32, OBS_FLAG string
    -> NUTS
Note: The data contains the "geo" codelist/attribute. This means we can add a geometry to the data.
Note: This Custom Transformer will add the NUTS geometries to the data. The attribute containing the GEO data has to be specified (default "geo"). / 3 extra Parameters can then be set. / 1) GeometryType - Points or Surfaces. / 2) Projection - The desired Coordinate system. / 3) Resolution - The desired resolution of the geometries. / Keep in mind that higher resolutions will decrease performance.
NUTS
    GEOTYPE = $(GEOTYPE)
    PROJ = $(PROJ)
    RES = $(RES)
    _GEO_ORG = @Value(geo)
    -> LookUp
Note: Translate the code values that are contained in the attributes to their actual meaning.
LookUp
    LANG = $(LANG)
    -> FMEFunctionCaller
    -> Junction
Junction
    -> Inspector
Inspector
Inspector_2

Bookmark: 2) Reading with a FeatureReader
Creator
    GEOMTYPE = Geometry Object
    NUM = 1
    CREATED -> FeatureReader [INITIATOR]
FeatureReader
    ATTRIBUTES = ORG_LSTSPEC,"DATAFLOW,""LAST UPDATE"",freq,animals,unit,geo,TIME_PERIOD,OBS_VALUE,OBS_FLAG"
    ATTR_ACCUM_MODE = Only Use Result
    COMBINE_GEOM = Use Result
    DATASET = fme://eea.fme-eurostat.fme-eurostat/ORG_LSTSPEC.csv?id=ORG_LSTSPEC&module=fmepy_eurostat.catalog&webservice=eea.eurostat.Eurostat&connection=sejuva%20Eurostat_v1%20(eea.eurostat)
    EEA.EUROSTAT.EUROSTAT_CASE_SENSITIVE_FIELD_NAMES = Yes
    EEA.EUROSTAT.EUROSTAT_CHUNK_SIZE = 100000
    EEA.EUROSTAT.EUROSTAT_DATE_INPUT_FORMAT = %d/%m/%y2099 %H:%M:%S$
    EEA.EUROSTAT.EUROSTAT_DELIMITER = ,
    EEA.EUROSTAT.EUROSTAT_ENCODING = UTF-8
    EEA.EUROSTAT.EUROSTAT_ENFORCE_STRICT_SCHEMA = No
    EEA.EUROSTAT.EUROSTAT_FEATURE_TYPE_NAME = FILE_NAME
    EEA.EUROSTAT.EUROSTAT_FIELD_NAMES_LINE = 1
    EEA.EUROSTAT.EUROSTAT_FIELD_QUALIFIER_CHARACTER = "
    EEA.EUROSTAT.EUROSTAT_FIELD_QUALIFIER_ESCAPE_CHARACTER = "
    EEA.EUROSTAT.EUROSTAT_PRESERVE_SOURCE_ENCODING = No
    EEA.EUROSTAT.EUROSTAT_QUERY_FEATURE_TYPES_FOR_MERGE_FILTERS = Yes
    EEA.EUROSTAT.EUROSTAT_READ_EMPTY_VALUES_AS = Null
    EEA.EUROSTAT.EUROSTAT_READ_SKIPPED_LINES = No
    EEA.EUROSTAT.EUROSTAT_REPLACE_ATTR_NAME_INVALID_CHARS = No
    EEA.EUROSTAT.EUROSTAT_SCAN_ADDITIONAL_FIELDS = No
    EEA.EUROSTAT.EUROSTAT_SCAN_TYPES = Yes
    EEA.EUROSTAT.EUROSTAT_SKIP_DUPLICATE_DELIMITERS = No
    EEA.EUROSTAT.EUROSTAT_STRING_TYPE_ATTRIBUTE_HANDLING = STANDARD_TYPES
    EEA.EUROSTAT.EUROSTAT_SUPPORTED_READER_ARCHIVE_EXTENSIONS = csv.gz,txt.gz
    EEA.EUROSTAT.EUROSTAT_TRIM_FEATURE_TYPE_NAME = Yes
    EEA.EUROSTAT.EUROSTAT_TRIM_FIELD_NAME_QUALIFIERS = Yes
    EEA.EUROSTAT.EUROSTAT_TRIM_FIELD_NAME_WHITESPACE = Yes
    EEA.EUROSTAT.EUROSTAT_TRIM_FIELD_VALUE_QUALIFIERS = Yes
    EEA.EUROSTAT.EUROSTAT_TYPE_ATTRIBUTE_HANDLING = STANDARD_TYPES
    EEA.EUROSTAT.EUROSTAT_USE_CUSTOM_SCHEMA = No
    FEATURETYPES = ORG_LSTSPEC
    FORMAT = EEA.EUROSTAT.EUROSTAT
    INTERACT = NONE
    OUTPUT_FEATURES_DISPLAY = Schema and Data Features
    ORG_LSTSPEC -> NUTS

Bookmark: PIVOT
FMEFunctionCaller
    FUNC = @SupplyAttributes(@Value(TIME_PERIOD),@Value(OBS_VALUE))
    -> AttributeRemover
AttributeRemover
    REMOVE_ATTRS = OBS_VALUE,TIME_PERIOD
    -> Aggregator
Note: Select all attributes from current dataset!
Aggregator
    ACCUM_ATTRS_NAME = Merge Incoming Attributes
    GROUP_BY = DATAFLOW fme_feature_type freq geo "LAST UPDATE" OBS_FLAG unit animals
    MODE = Attributes Only
    SEP = ,
    AGGREGATE -> AttributeExposer
Note: Add the time_periods that you want to expose
AttributeExposer
    ATTR_LIST = 2012,2013,2014,2015,2016,2017,2018,2019,2020,2021
    -> Inspector_2

Bookmark: 3) Using N observations filter
Note: Organic Livestock with First and Last N observations set to 1
Note: Due to the N observations set to 1 in both cases, the data now only contains values that were recorded in 2012 (first observation) and 2021 (last observation). The data still contains several hundred features due to the fact that the combinations of Geo and animal is unique per these years.
ORG_LSTSPEC_d8bb3647 (reader EEA.EUROSTAT.EUROSTAT_2) [off]
    attributes: DATAFLOW string, LAST UPDATE datetime, freq string, animals string, unit string, geo string, TIME_PERIOD uint32, OBS_VALUE uint32, OBS_FLAG string
    -> NUTS_2 [off]
NUTS_2
    GEOTYPE = $(GEOTYPE)
    PROJ = $(PROJ)
    RES = $(RES)
    _GEO_ORG = @Value(geo)
    -> LookUp_2
LookUp_2
    LANG = $(LANG)
    -> Inspector_3

Bookmark: Month
Note: Euro yield curves - Monthly data / Start_period: 2016-04 / End_period: 2016-06
IRT_EURYLD_M_ed470f15 (reader EEA.EUROSTAT.EUROSTAT_6) [off]
    attributes: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
Note: Euro yield curves - Monthly data / Start_period: 2016-M04 / End_period: 2016-M06
IRT_EURYLD_M_970c2537 (reader EEA.EUROSTAT.EUROSTAT_7) [off]
    attributes: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

Bookmark: Day
Note: Euro yield curves - daily data / Start_period: 2023-03-28 / End_period: 2023-03-29
IRT_EURYLD_D_8f338484 (reader EEA.EUROSTAT.EUROSTAT_3) [off]
    attributes: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

Bookmark: 05) Readying several datasets with a Parent/hildWorkspace
Creator_2 [off]
    GEOMTYPE = Geometry Object
    NUM = 1
    CREATED -> WorkspaceRunner [off]
WorkspaceRunner [off]
    BLOCKING = No
    MAX_TO_BATCH = 1
    WORKSPACE_FILE = $(FME_MF_DIR)ChildWorkspace.fmw
    WORKSPACE_PARAMETERS = EurostatWebConnection,sejuva Eurostat_v1 (eea.eurostat),Datasets,ORG_LSTSPEC,IRT_EURYLD_M,Box,FME_DISCLOSURE_OPEN,FirstNObservations,1,LastNObservations,1,StartPeriod,,EndPeriod,,DestDataset_JSON,C:\Users\SEJUVA\Downloads\WorkspacerunnerOutput.json

Bookmark: In Development. More effective LookUp for code values
MAR_GO_QM_EE (reader EEA.EUROSTAT.EUROSTAT_5)
    attributes: DATAFLOW string, LAST UPDATE datetime, freq string, direct string, cargo string, unit string, par_mar string, rep_mar string, TIME_PERIOD string, OBS_VALUE uint32, OBS_FLAG string
    -> LookUpV2
Note: In development. Attribute names will be kept original and preferebly build into the reader
LookUpV2
    -> AttributeExposer_2_Output
AttributeExposer_2_Output: Inspector

Bookmark: Year
Note: Daily smokers of cigarettes by sex, age and degree of urbanisation. / Start_period: 2014 / End_period: 2014
HLTH_EHIS_SK3U_41296021 (reader EEA.EUROSTAT.EUROSTAT_4) [off]
    attributes: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

FME custom transformer LookUpV2
In development

Input (input)
    -> AttributeKeeper
AttributeKeeper
    CREATE_BULK_MODE_FEATURES = NO
    KEEP_ATTRS = DATAFLOW
    -> PythonCaller_Original_2
PythonCaller_Original_2
    PYTHONSOURCE:
      import requests
      import xml.etree.ElementTree as ET
      import fme
      import fmeobjects


      class FeatureProcessor(object):
          def __init__(self):
              pass

          def input(self, feature):
              indata = feature.getAttribute('DATAFLOW')
              indata = indata.replace('(', ':')
              self.data = indata.split(':')[1]
              print(self.data)

          def close(self):
              url_d = 'https://ec.europa.eu/eurostat/api/dissemination/sdmx/2.1/data/' + self.data
              url_md = 'https://ec.europa.eu/eurostat/api/dissemination/sdmx/2.1/dataflow/ESTAT/' + self.data + '?references=descendants'
              response_d = requests.get(url_d)
              response_md = requests.get(url_md)
              root_d = ET.fromstring(response_d.content)
              root_md = ET.fromstring(response_md.content)

              # Build a dictionary with all of the variable names
              concepts = {}
              for i in root_md.iter('{http://www.sdmx.org/resources/sdmxml/schemas/v2_1/structure}Concept'):
                  for j in i:
                      if 'Name' in j.tag and j.attrib['{http://www.w3.org/XML/1998/namespace}lang'] == 'en':
                          concepts[i.attrib['id']] = j.text

              # Build a dictionary with all of the codes used in the dataset
              codes = {}
              for i in root_md.iter('{http://www.sdmx.org/resources/sdmxml/schemas/v2_1/structure}Code'):
                  for j in i:
                      if j.attrib['{http://www.w3.org/XML/1998/namespace}lang'] == 'en':
                          codes[i.attrib['id']] = j.text

              # Build a variable with the dataset name
              for i in root_md.iter('{http://www.sdmx.org/resources/sdmxml/schemas/v2_1/structure}Dataflow'):
                  for j in i.iter('{http://www.sdmx.org/resources/sdmxml/schemas/v2_1/common}Name'):
                      if 'Name' in j.tag and j.attrib['{http://www.w3.org/XML/1998/namespace}lang'] == 'en':
                          dataset = j.text

              # Build a variable with the dataflow name and version
              for i in root_d.iter('{http://www.sdmx.org/resources/sdmxml/schemas/v2_1/common}StructureUsage'):
                  for j in i:
                      dataseries = j.attrib['id'] + '_' + j.attrib['agencyID'] + '_' + j.attrib['version']

              # skapa värde för LAST UPDATE
              for i in root_d.iter('{http://www.sdmx.org/resources/sdmxml/schemas/v2_1/message}Prepared'):
                  prepared = i.text

              # skapa attribut för TIME_PERIOD
              for i in root_d.iter('{http://www.sdmx.org/resources/sdmxml/schemas/v2_1/message}Structure'):
                  dimension = i.attrib['dimensionAtObservation']
                  if dimension in concepts:
                      dimension = concepts[dimension]

              for series in root_d.iter('{http://www.sdmx.org/resources/sdmxml/schemas/v2_1/data/generic}Series'):
                  for serieskey in series.iter('{http://www.sdmx.org/resources/sdmxml/schemas/v2_1/data/generic}SeriesKey'):
                      template_feature = fmeobjects.FMEFeature()
                      for key_val in serieskey.iter('{http://www.sdmx.org/resources/sdmxml/schemas/v2_1/data/generic}Value'):
                          if key_val.attrib['id'] in concepts:
                              id = concepts[key_val.attrib['id']]
                          if key_val.attrib['value'] in codes:
                              val = codes[key_val.attrib['value']]
                          template_feature.setAttribute(id, val)

                  for obs in series.iter('{http://www.sdmx.org/resources/sdmxml/schemas/v2_1/data/generic}Obs'):
                      for dim in obs.iter('{http://www.sdmx.org/resources/sdmxml/schemas/v2_1/data/generic}ObsDimension'):
                          new_feature = template_feature.clone()
                          new_feature.setAttribute(dimension, dim.attrib['value'])

                      for j in obs:
                          if 'Attributes' in j.tag:
                              for k in j:
                                  if k.attrib['id'] in concepts:
                                      id = concepts[k.attrib['id']]
                                  if k.attrib['value'] in codes:
                                      val = codes[k.attrib['value']]
                                  new_feature.setAttribute(id, val)

                      for val in obs.iter('{http://www.sdmx.org/resources/sdmxml/schemas/v2_1/data/generic}ObsValue'):
                          new_feature.setAttribute('Dataset', dataset)
                          new_feature.setAttribute('Observation value', val.attrib['value'])
                          new_feature.setAttribute('LAST UPDATE', prepared)
                          new_feature.setAttribute('DATAFLOW', dataseries)

                          self.pyoutput(new_feature)

              pass
    PYTHONSYMBOL = FeatureProcessor
    -> AttributeExposer_2
AttributeExposer_2
    ATTR_LIST = Dataset,"LAST UPDATE","Observation value",Time,"Time frequency","Unit of measure","Direction of flow","Maritime entity (partner)","Maritime entity (reporting)","Type of cargo"
    -> Output (output)
Output (output)

FME custom transformer LookUp

Parameters:
- LANG = NO   # NO LOOKUP,NO%English,en%Francais,fr%Deutsch,de Select Language

Input (input)
    -> Junction_2
Output (output)

Bookmark: Do look up
Junction_2
    -> Sampler
    -> FeatureMerger [REQUESTOR]
Note: Call codelists
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://ec.europa.eu/eurostat/api/dissemination/sdmx/2.1/codelist/ESTAT/@Value(name)
    TRANSFER_TIMEOUT_LENGTH = 90
    USE_COOKIES = No
    VERIFY_SSL_CERTIFICATES = Yes
    -> XMLFragmenter
    <REJECTED> -> HTTPCaller__Rejected_
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> EurostatLoopedLookUp [DataRows]
EurostatLoopedLookUp
    NAME = @Value(name)
    _ATTRIBUTES_COUNT = @Value(_attributes_count)
    -> AttributeRemover
AttributeRemover
    LIST_ATTRS = _attributes{}
    REMOVE_ATTRS = _attributes_count,name
    -> Output (output)
HTTPCaller__Rejected_: Logger
    LOG_FEATURE = LOG_ONLY
    MAXCOORDS = 20
    MAXFEATS = 20
    MESSAGE = Feature is:
    SEVERITY = INFO

Bookmark: Identify attributes to look up
Sampler
    RATE = 1
    SAMPLE_MODE = No
    SAMPLE_TYPE_LONG = First N Features
    SAMPLED -> SchemaScanner
SchemaScanner
    CASE = No
    EMPTY_ATTR_HANDLING = SCANNER_DEFAULT
    HOLD = Yes
    SCHEMA_NAME_ATTR = fme_feature_type_name
    UNBOUNDED_NUMBERS = Yes
    UNBOUNDED_STRINGS = No
    <SCHEMA> -> ListExploder
ListExploder
    ATTR_ACCUM_MODE = Merge List Attributes
    ATTR_CONFLICT_RES = Use List Attribute Values
    INDEX_ATTR = _element_index
    LIST_ATTR = attribute{}
    ELEMENTS -> Tester
Tester
    BOOL_OP = COMPOSITE
    COMPOSITE_TEST = 1 AND 2
    TEST_CLAUSE:
      TEST @Value(name) NOT_IN DATAFLOW,LAST UPDATE,TIME_PERIOD,OBS_VALUE,Source Brancher 0.BranchingFactory.Count,Source Feature Router.BranchingFactory.Count
      CASE_SENSITIVE_TEST @Value(name) NOT_CONTAINS_REGEX ^(csv|fme|eurostat|multi)?\_
    TEST_MODE = PER_TEST
    PASSED -> HTTPCaller

Bookmark: Trim down code list
XMLFragmenter
    ATTRIBUTE_XML = _response_body
    EMBEDDED_EXPRESSIONS = Structure/Structures/Codelists/Codelist/Code
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = Code.id
    REJECT_FEATURES_WITH_NO_FRAGMENTS = YES
    XML_SOURCE_TYPE = Attribute with XML document
    FRAGMENTS -> AttributeExposer
AttributeExposer
    ATTR_LIST = Name{},Name{}.lang
    -> ListSearcher
ListSearcher
    ATTR_VALUE = $(LANG)
    CASE = CASE_SENSITIVE
    INDEX_ATTR = _list_index
    LIST_ATTR = Name{}.lang
    MATCHTYPE = FIRST_MATCHED_ENCODED
    FOUND -> AttributeCreator
    NOT_FOUND -> AttributeCreator_2
AttributeCreator
    ATTR_TABLE = SET_TO _literal = @Value(Name{@Value(_list_index)})
    -> AttributeRenamer
AttributeCreator_2
    ATTR_TABLE = SET_TO _literal = @Value(Name{0})
    -> AttributeRenamer
AttributeRenamer
    ATTR_TABLE = RENAME_SET_DEFAULT Code.id > _code
    MISSING_INPUT_ATTRS = REMOVE
    -> AttributeKeeper
AttributeKeeper
    CREATE_BULK_MODE_FEATURES = NO
    KEEP_ATTRS = name,_code,_literal
    -> Aggregator
Aggregator
    ACCUM_ATTRS_NAME = Drop Incoming Attributes
    AGGREGATE_TYPE = Homogeneous Collection (If Possible)
    GROUP_BY = name
    LIST_ATTRS_TO_INCLUDE = _code _literal
    LIST_NAME = _codes
    MODE = Geometry - Assemble One Level
    SEP = ,
    AGGREGATE -> EurostatLoopedLookUp [CodeLists]
    AGGREGATE -> Aggregator_2
Aggregator_2
    ACCUM_ATTRS_NAME = Drop Incoming Attributes
    AGGREGATE_TYPE = Homogeneous Collection (If Possible)
    LIST_ATTRS_TO_INCLUDE = name
    LIST_NAME = _attributes
    MODE = Geometry - Assemble One Level
    SEP = ,
    AGGREGATE -> ListElementCounter
ListElementCounter
    CNT_ATTR = _attributes_count
    LIST_NAME = _attributes{}
    -> FeatureMerger [SUPPLIER]

FME custom transformer NUTS

Parameters:
- _GEO_ORG = @Value(_geo_org)   # Geo
- GEO_GRP = FME_DISCLOSURE_OPEN   # Geometry selection
- GEOTYPE = RG   # Select geometry type
- PROJ = 4326
- RES = 20M   # 60 m,60M%20 m,20M%10 m,10M%3 m,03M%1 m,01M Select surface resolution

Input (input)
    -> AttributeExposer
AttributeExposer
    ATTR_LIST = TIME_PERIOD
    -> AttributeCreator_year
FeatureJoiner
    ATTR_CONFLICT_RES = Prefer Left
    GEOMETRY_HANDLING = Prefer Left
    JOIN_MODE = Inner

Bookmark: Handle geometries
AttributeCreator_year
    ATTR_TABLE = SET_TO _year = @Left(@Value(TIME_PERIOD),4)
    -> AttributeRangeMapper_NUTS_versions
Note: Would be good to find a look-up for this.
AttributeRangeMapper_NUTS_versions
    IN_ATTR = _year
    LUT = 2003,2007,2003,2008,2011,2006,2012,2014,2010,2015,2017,2013,2018,2020,2016,2021,,2021,,,
    OUT_ATTR = _nuts_ver
    -> FeatureMerger [REQUESTOR]
    -> Tester
Tester
    BOOL_OP = OR
    TEST_CLAUSE = NUM_TEST @Value(_nuts_ver) >= 2003
    TEST_MODE = NUM_TEST
    PASSED -> DuplicateFilter_NUTS
DuplicateFilter_NUTS
    INPUT_ORDERED_CHOICE = No
    KEYATTR = _nuts_ver
    UNIQUE -> AttributeKeeper_NUTS
AttributeKeeper_NUTS
    CREATE_BULK_MODE_FEATURES = NO
    KEEP_ATTRS = _nuts_ver
    -> TestFilter_GEOTYPE
TestFilter_GEOTYPE
    DEFAULT_VALUE = Label points
    PASSED_TEST_GROUP_OUTPUT = FIRST
    TEST_LIST = "BOOL_OP,OR,COMPOSITE_TEST,""""""1"""""",TEST_CLAUSE,TEST $(GEOTYPE) = RG",Regions
    Regions -> FeatureReader_NUTS_RG [INITIATOR]
    Label points -> FeatureReader_NUTS_LB [INITIATOR]
FeatureReader_NUTS_RG
    ATTRS_TO_EXPOSE = _nuts_ver id
    ATTR_ACCUM_MODE = Merge Initiator and Result
    ATTR_CONFLICT_RES = Use Result
    ATTR_IGNORE_NULLS = No
    COMBINE_GEOM = Use Result
    DATASET = https://gisco-services.ec.europa.eu/distribution/v2/nuts/geojson/NUTS_RG_$(RES)_@Value(_nuts_ver)_$(PROJ).geojson
    FORMAT = GEOJSON
    GEOJSON_FLATTEN_MODE = ALL_LEVELS
    GEOJSON_USE_BASENAME_AS_DEFAULT_FEATURE_TYPE = Yes
    GEOJSON_USE_SEARCH_ENVELOPE = NO
    INTERACT = NONE
    OUTPUT_FEATURES_DISPLAY = Schema and Data Features
    <OTHER> -> FeatureMerger [SUPPLIER]
    <REJECTED> -> Junction
Junction
FeatureReader_NUTS_LB
    ATTRS_TO_EXPOSE = _nuts_ver id
    ATTR_ACCUM_MODE = Merge Initiator and Result
    ATTR_CONFLICT_RES = Use Result
    ATTR_IGNORE_NULLS = No
    COMBINE_GEOM = Use Result
    DATASET = https://gisco-services.ec.europa.eu/distribution/v2/nuts/geojson/NUTS_LB_@Value(_nuts_ver)_$(PROJ).geojson
    FORMAT = GEOJSON
    GEOJSON_FLATTEN_MODE = ALL_LEVELS
    GEOJSON_USE_BASENAME_AS_DEFAULT_FEATURE_TYPE = Yes
    GEOJSON_USE_SEARCH_ENVELOPE = NO
    INTERACT = NONE
    OUTPUT_FEATURES_DISPLAY = Schema and Data Features
    <OTHER> -> FeatureMerger [SUPPLIER]
FeatureMerger
    ATTR_ACCUM_MODE = Merge Supplier
    ATTR_CONFLICT_RES = Use Requestor
    IGNORE_NULLS = No
    JOIN_KEYS = @Value(_nuts_ver) @Value(_nuts_ver) AUTO @Value(_geo_org) @Value(id) AUTO
    MERGE_TYPE = Attributes and Geometry
    PROCESS_DUPS = NO
    REJECT_NULL_MISSING_KEYS = No
    SUPPLIERS_FIRST = No
    MERGED -> Aggregator [off]
    MERGED -> AttributeRemover
    UNMERGED_REQUESTOR -> Aggregator_2 [off]
    UNMERGED_REQUESTOR -> AttributeRemover
AttributeRemover
    REMOVE_ATTRS = _nuts_ver,_year,_geo_org,id
    -> Output (output)
Output (output)
Aggregator [off]
    ACCUM_ATTRS_NAME = Drop Incoming Attributes
    AGGREGATE_TYPE = Homogeneous Collection (If Possible)
    COUNT_ATTR = _count
    GROUP_BY = _geo_org
    MODE = Geometry - Assemble One Level
    SEP = ,
Note: We need to find geometries for aggregates of countries, ie EU, EFTA, Europe etc.
Aggregator_2 [off]
    ACCUM_ATTRS_NAME = Drop Incoming Attributes
    AGGREGATE_TYPE = Homogeneous Collection (If Possible)
    COUNT_ATTR = _count
    GROUP_BY = _geo_org
    MODE = Geometry - Assemble One Level
    SEP = ,
